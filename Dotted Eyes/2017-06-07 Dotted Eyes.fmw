FME workspace 2017-06-07 Dotted Eyes.fmw
Title: Format & Projection Setter / Creator
Description: Create Formats for the Update Cycle UK data only
Formats created:
Shape
MapInfo TAB
MapInfo MIF
CSV
Projections generated:
OSGB
LL WGS84
Usage: Add MapInfo Files into the SOURCE folder
Disable any formats not required
If CSV is required Check the varables are setup inthe Attributecreator and Stringreplacer for both projection streams
History: 06/01/15,Neil Carr,Created v1,07/01/15,Neil Carr,Fixes applied v2,15/01/15,Neil Carr,Fixess applied - LL wrong way round

Parameters:
- Release_Number =   # What is the release Number
- BT_DPD_ZIP_FOLDER_In = $(FME_MF_DIR)Program Output\Custom Geopoint   # ZIP FOLDER 1 In
- BT_DPD_ZIP_FOLDER_Out = $(FME_MF_DIR)Program Output\$(Release_Number)_Custom_Geopoint   # ZIP FOLDER 1 Out

Readers:
- MAPINFO_1: MAPINFO from $(FME_MF_DIR)SOURCE\**\*.tab

Writers:
- CSV_1: CSV to $(FME_MF_DIR)Program Output\Custom Geopoint
- CSV_2: CSV to $(FME_MF_DIR)Program Output\Custom Geopoint

Note: Instructions / 1) Unzip Geopoint standard product into the source folder / 2) Use the 'Prompt and Run Workspace option to run the Program / 3) Insert which release you are creating e.g. R64 / 4) Outputs will be directed into the 'Program Output' folder / 5) Disable Reader (From Navigation Panel) / Vstreet Creator and enable Zip Creator transformer / 6) Re-run workspace to zip up All contents
ANY PRODUCT TAB (reader MAPINFO_1)
    -> TestFilter_2

Bookmark: Dotted Eyes
TestFilter_2
    DEFAULT_VALUE = <UNFILTERED>
    TEST_LIST = BOOL_OP,OR,COMPOSITE_TEST,<Unused>,TEST_CLAUSE,"TEST @Value(POSTAREA) = GY",GY,BOOL_OP,OR,COMPOSITE_TEST,<Unused>,TEST_CLAUSE,"TEST @Value(POSTAREA) = JE",JE
    GY -> AttributeCreator_2
    JE -> AttributeCreator_3
AttributeCreator_2
    ATTR_LIST = Dotted_Eyes_GY,@Value(fme_basename)_GY
    -> CSV_Formatter_8 [GeometryFilter_3_Input]
CSV_Formatter_8: CSV Formatter
    StringReplacer_2_Output -> Discards (writer CSV_1)
Discards (writer CSV_1)
AttributeCreator_3
    ATTR_LIST = Dotted_Eyes_JE,@Value(fme_basename)_JE
    -> CSV_Formatter_2 [GeometryFilter_3_Input]
CSV_Formatter_2: CSV Formatter
    StringReplacer_2_Output -> Vstreets (writer CSV_2)
Vstreets (writer CSV_2)

Bookmark: Zip Archiver
Zip_Creator: Creator [off]
    NUM = 1
    GEOMTYPE = Geometry Object
    CREATED -> ZipArchiver
ZipArchiver
    FILE_PATH = $(BT_DPD_ZIP_FOLDER_In)
    ZIP_PATH = $(BT_DPD_ZIP_FOLDER_Out)
    MODE = APPEND
    -> ZipArchiver_Output
    LogSuccess -> ZipArchiver_LogSuccess
    LogFailure -> ZipArchiver_LogFailure
ZipArchiver_Output: Inspector
ZipArchiver_LogSuccess: Inspector
ZipArchiver_LogFailure: Inspector

FME custom transformer SH

GeometryFilter_Input_1 (input)
GeometryFilter_Point_1 (output)
GeometryFilter_Line_1 (output)
GeometryFilter_Area_1 (output)
GeometryFilter_Null_1 (output)

FME custom transformer CSV Formatter

GeometryFilter_3_Input (input)
    -> GeometryFilter_3
GeometryFilter_3
    BREAK_AGG = No
    INSTANTIATE = No
    GEOM_PORT_NAMES = Point Line Area Null
    POINT -> AttributeCreator_2
    NULL -> AttributeCreator_2
AttributeCreator_2
    ATTR_LIST = POSTCODE,"@Value(POSTCODE)",GEO_UNIT,"@Value(GEO_UNIT)",COM_UNIT,"@Value(COM_UNIT)",GEO_SUB,"@Value(GEO_SUB)",COM_SUB,"@Value(COM_SUB)",GEO_SECT,"@Value(GEO_SECT)",COM_SECT,"@Value(COM_SECT)",GEO_DIST,"@Value(GEO_DIST)",COM_DIST,"@Value(COM_DIST)",POSTAREA,"@Value(POSTAREA)",PO_BOX,"@Value(PO_BOX)",POS_QUAL,"@Value(POS_QUAL)",USER,"@Value(USER)",NHS,"@Value(NHS)",NHS_R,"@Value(NHS_R)",POSTTOWN,"@Value(POSTTOWN)",WARD,"@Value(WARD)",COUNTY,"@Value(COUNTY)",COUNTRY,"@Value(COUNTRY)",T_COUNTY,"@Value(T_COUNTY)",P_COUNTY,"@Value(P_COUNTY)",A_COUNTY,"@Value(A_COUNTY)",START_SECTOR,"@Value(START_SECTOR)",DEST_SECTOR,"@Value(DEST_SECTOR)",Locator_Sector,"@Value(Locator_Sector)",Neighbouring_Sector,"@Value(Neighbouring_Sector)",CONGESTION_BOUNDARY,"@Value(CONGESTION_BOUNDARY)",VSTREET,"@Value(VSTREET)",DISCARD,"@Value(DISCARD)",sector,"@Value(sector)",sector1,"@Value(sector1)",SECTOR,"@Value(SECTOR)",DISTRICT,"@Value(DISTRICT)",DISTRICT_NAME,"@Value(DISTRICT_NAME)",AREA,"@Value(AREA)",ISBA_ID,"@Value(ISBA_ID)",ISBA_NAME,"@Value(ISBA_NAME)",BARB_NAME,"@Value(BARB_NAME)",ILR_RADIO_ID,"@Value(ILR_RADIO_ID)",ILR_RADIO_NAME,"@Value(ILR_RADIO_NAME)",BBC_RADIO_ID,"@Value(BBC_RADIO_ID)",BBC_RADIO_NAME,"@Value(BBC_RADIO_NAME)",PAPER_NAME,"@Value(PAPER_NAME)",TYPE,"@Value(TYPE)",FREQUENCY,"@Value(FREQUENCY)",Locator_District,"@Value(Locator_District)",Neighbouring_District,"@Value(Neighbouring_District)",OA,"@Value(OA)",OutputArea,"@Value(OutputArea)",OUTPUT_AREA,"@Value(OUTPUT_AREA)",OUTWARD_CODE,"@Value(OUTWARD_CODE)",INWARD_CODE,"@Value(INWARD_CODE)",GEOGRAPHIC,"@Value(GEOGRAPHIC)",STATUS,"@Value(STATUS)"
    -> StringReplacer_2
StringReplacer_2
    SRC_ATTRS = A_COUNTY,AREA,BARB_NAME,BBC_RADIO_ID,BBC_RADIO_NAME,COM_DIST,COM_SECT,COM_SUB,COM_UNIT,CONGESTION_BOUNDARY,COUNTRY,COUNTY,DEST_SECTOR,DISCARD,DISTRICT,DISTRICT_NAME,FREQUENCY,GEO_DIST,GEO_SECT,GEO_SUB,GEO_UNIT,ILR_RADIO_ID,ILR_RADIO_NAME,INWARD_CODE,ISBA_ID,ISBA_NAME,Locator_District,Locator_Sector,Neighbouring_District,Neighbouring_Sector,NHS,NHS_R,OA,OUTPUT_AREA,OutputArea,OUTWARD_CODE,P_COUNTY,PAPER_NAME,PO_BOX,POS_QUAL,POSTAREA,POSTCODE,POSTTOWN,sector,SECTOR,sector1,START_SECTOR,T_COUNTY,TYPE,USER,VSTREET,WARD,GEOGRAPHIC
    FIND_TEXT = ""
    REGEXP = no
    NO_MATCH = _FME_NO_OP_
    CASE = no
    -> StringReplacer_2_Output (output)
StringReplacer_2_Output (output)

FME custom transformer ZipArchiver
Compresses a file or folder and appends it into the specified zip file.
    The archive name will be the same as the target file name. If a file having the same name as the target file has been archived in the zip file already, the file will not be archived.
    The transformer creates a new zip file when receiving the first file that should be archived into it, if the specified zip file doesn't exist. 
    -----
    Note: This transformer has been basically internationalized with 2016-01-22 update. However, depending on the environment (platform, OS version etc.), file path strings containing Non-ASCII characters still may not be treated correctly. Please test enough if the path strings may contain Non-ASCII characters.
    -----
    Input features will be output through the Output port as-is.
    The transformer creates log features which contain these attributes for each file, and outputs them from the LogSuccess/LogFailure port.
    - Result: "success" if the file was archived successfully, "failure" otherwise.
    - Target File: the target file path.
    - Zip File: the zip file path.
    - Archive Name: the archive name of the target file in the zip file if archived successfully, empty otherwise.
    - Comment: compression ratio if archived successfully, failure reason otherwise.
    ファイルまたはフォルダを圧縮し、指定したzipファイルに追加します。
    アーカイブ名は対象のファイル名と同じになります。対象とするファイルと同じ名前のファイルがすでにzipファイルにアーカイブされていた場合、そのファイルはアーカイブされません。
    指定したzipファイルが存在しない場合、このトランスフォーマーはそれにアーカイブすべき最初のファイルを受け取ったときに新しいzipファイルを作成します。
-----
    注: 2016-01-22 の更新によって、このトランスフォーマーは基本的には国際化されました。しかし、環境（プラットフォームやOSのバージョンなど）によっては、ASCII文字（半角の英数字や記号）以外の文字を含むファイルパス文字列ま、まだ正しく処理されない可能性があります。パス文字列に非ASCII文字が含まれる可能性がある場合は、十分にテストしてください。
-----
    入力フィーチャーはそのままOutputポートから出力されます。
    このトランスフォーマーは、次の属性を持つログフィーチャーをファイルごとに作成し、LogSuccess/LogFailureポートから出力します。
    - Result: ファイルが正常にアーカイブされた場合は"succcess"、そうでない場合は"failure"
    - Target File: 対象のファイルパス
    - Zip File: zipファイルパス
    - Archive Name: アーカイブに成功した場合はzipファイル内でのアーカイブ名、失敗した場合は空文字列
    - Comment: アーカイブに成功した場合は圧縮率、失敗した場合はその理由
Parameters 
    Target File or Folder
    : 
    Specify a file or folder path that should be archived. You can also set a feature attribute value to this parameter.
    If you specify a folder path here, all files under the folder will be archived. In the case, the original directory structure will also be preserved, and the archive name of the file will contain path starting from the specified folder.
    アーカイブするファイルまたはフォルダのパスを指定します。フィーチャーの属性をこのパラメーターに設定することもできます。 
    ここにフォルダのパスを指定した場合は、そのフォルダ以下にある全てのファイルがアーカイブされます。その場合、元のディレクトリ構造も維持され、ファイルのアーカイブ名には、指定されたフォルダから始まるパスが含まれます。
    Destination Zip File
    : 
    Specify a zip file path (*.zip). You can also set a feature attribute value to this parameter.
    If the extension of the specified file path is not "zip", the transformer will add ".zip" to the path automatically. 
    zipファイルパス（*.zip）を指定します。フィーチャーの属性をこのパラメーターに設定することもできます。 
    指定されたパスの拡張子が"zip"でない場合は、そのパスに".zip"を自動的に付加します。
    If Destination Zip File Exists
    :
    If the specified destination zip file exists at the translation starting time, this transformer appends compressed files into the existing zip file, by default. If you set 
    "Remove Existing Zip File"
    to this parameter, this transformer removes the existing zip file once at first, and then appends compressed files into the newly created same name zip file. If you set 
    "Rename Destination Zip File"
    , an suffix will be added to the destination zip file name automatically to differentiate from the existing zip file.
    変換の開始時に指定されたzipファイルが存在する場合、デフォルトでは、このトランスフォーマーは既存のzipファイルに圧縮したファイルを追加します。このパラメーターに 
    "Remove Existing Zip File"
    を設定した場合は、このトランスフォーマーは最初に一回だけ既存のzipファイルを削除してから、新たに作成した同じ名前のzipファイルに圧縮したファイルを追加します。
    "Rename Destination Zip File"
    を設定した場合は、既存のzipファイルと区別するため、出力先のzipファイル名にサフィクスが自動的に付加されます。

Parameters:
- FILE_PATH =   # Target File or Folder
- ZIP_PATH =   # Destination Zip File
- MODE = APPEND

Input (input)
    -> ParameterFetcher
ParameterFetcher
    ATTR_LIST = __ziparchiver.filepath {$(FILE_PATH)} __ziparchiver.zippath {$(ZIP_PATH)} __ziparchiver.mode {$(MODE)}
    -> PythonCaller
PythonCaller
    NEW_ATTRIBUTES = __ziparchiver.result
    PYTHONSOURCE:
      import fme
      import fmeobjects
      import os, zipfile, locale

      # 2015-05-24  Takashi Iijima  Original Implementation
      # 2016-01-22  Takashi Iijima  Refactoring and Internationalizing (Tech Preview)

      class ZipArchiver(object):
          def __init__(self):
              t = locale.getdefaultlocale()
              self.encode = lambda s: (s.encode(t[1]) if t else s) if isinstance(s, unicode) else s
              self.logger = fmeobjects.FMELogFile()
              self.zpaths = {} # key: specified zip file path (lower-case), value: treated zip file path in this session

          def input(self, feature):
              try:
                  # Retrieve target file path and zip file path from feature attributes.
                  # If the specified zip file path doesn't end with ".zip", add the extension.
                  regulatePath = lambda path: os.path.abspath(path).replace('\\', '/')
                  fpath = regulatePath(feature.getAttribute('__ziparchiver.filepath'))
                  zpath = regulatePath(feature.getAttribute('__ziparchiver.zippath'))
                  if not zpath.lower().endswith('.zip'):
                      zpath = '%s.zip' % zpath
                  keyPath = zpath.lower()

                  mode = feature.getAttribute('__ziparchiver.mode')
                  if os.path.exists(zpath):
                      if mode == 'REMOVE':
                          if keyPath not in self.zpaths:
                              os.remove(zpath)
                      elif mode == 'RENAME':
                          if keyPath in self.zpaths:
                              zpath = self.zpaths[keyPath]
                          else:
                              format, n = '%s_%d.zip', 1
                              while os.path.exists(format % (zpath[:-4], n)): n += 1
                              zpath = format % (zpath[:-4], n)
                  self.zpaths[keyPath] = zpath

                  # Collect  target file paths, including empty directries if "fpath" is a directory.
                  # If specifid file/directory doesn't exist, throw an error.
                  root = ''
                  fpaths, dpaths = [], []
                  if os.path.exists(fpath): # fpath is a file
                      root = os.path.split(fpath)[0]
                      if os.path.isfile(fpath):
                          fpaths = [fpath]
                      elif os.listdir(fpath): # fpath is a non-empty directory
                          for dirpath, dirnames, filenames in os.walk(fpath):
                              paths = [os.path.join(dirpath, d) for d in dirnames]
                              dpaths += [regulatePath(path) for path in paths if not os.listdir(path)]
                              fpaths += [regulatePath(os.path.join(dirpath, f)) for f in filenames]
                      else: # fpath is an empty directory
                          dpaths = [fpath]
                  else:
                      raise Exception('specified file doesn\'t exist.')

                  # If destination directory doesn't exist, create the directory.
                  if not os.path.exists(os.path.split(zpath)[0]):
                      os.makedirs(os.path.split(zpath)[0])

                  # Then, perform archiving.
                  with zipfile.ZipFile(zpath, 'a', zipfile.ZIP_DEFLATED) as zipper:
                      for path in [path for path in fpaths if path.lower() != zpath.lower()]:
                          aname = path[len(root) + 1:] # archive name
                          result, msg = False, ''
                          try:
                              info = zipper.getinfo(aname)
                              msg = '"%s" exists in the archive already.' % aname
                          except:
                              try:
                                  zipper.write(path, aname)
                                  info = zipper.getinfo(aname)
                                  after = info.compress_size/1024.0
                                  before = info.file_size/1024.0
                                  msg = '%.1f%% (%.1f/%.1fKB)' % (after/before*100.0, after, before)
                                  result = True
                              except Exception as ex:
                                  msg = '%s' % ex
                          self.outputLogFeature('Success' if result else 'Failure', path, zpath, aname, msg)
                      for path in dpaths:
                          aname = path[len(root) + 1:] # archive name
                          try:
                              info = zipper.getinfo(aname)
                          except:
                              zipper.write(path, aname)
              except Exception as ex:
                  self.outputLogFeature('Terminate', fpath, zpath, '', '%s' % ex)
              finally: # always output the input feature through the Output port.
                  self.pyoutput(feature)

          # Output a log feature.
          def outputLogFeature(self, flag, fpath, zpath, aname, msg):
              if flag != 'Success':
                  self.logger.logMessageString(self.encode('ZipArchiver: %s' % msg), \
                      fmeobjects.FME_ERROR if flag == 'Terminate' else fmeobjects.FME_WARN)
              feature = fmeobjects.FMEFeature()
              feature.setAttribute('__ziparchiver.result', flag.lower())
              feature.setAttribute('Target File', fpath)
              feature.setAttribute('Zip File', zpath)
              feature.setAttribute('Archive Name', aname if flag == 'Success' else '')
              feature.setAttribute('Comment', msg)
              feature.setAttribute('fme_feature_type', 'ZipArchiver_%s' % flag)
              self.pyoutput(feature)
    PYTHONSYMBOL = ZipArchiver
    -> Tester
Tester
    TEST_CLAUSE = TEST __ziparchiver.result ATTRIBUTE_IS_MISSING ""
    BOOL_OP = OR
    TEST_MODE = Automatic
    TEST_DESCRIPTION = ""
    PASSED -> Output (output)
    FAILED -> AttributeRenamer
Output (output)
AttributeRenamer
    ATTR_LIST = __ziparchiver.result,Result,
    -> AttributeExposer
AttributeExposer
    ATTR_LIST = "Target File","Zip File","Archive Name",Comment
    -> AttributeKeeper
AttributeKeeper
    KEEP_ATTRS = Archive Name,Comment,Result,Target File,Zip File
    -> AttributeFilter
AttributeFilter
    ATTR_VALUES = success,failure,terminate,<EMPTY>,<MISSING>,<NULL>,<UNFILTERED>
    ATTR_NAME = Result
    success -> LogSuccess (output)
    failure -> LogFailure (output)
    terminate -> Terminator
LogSuccess (output)
LogFailure (output)
Terminator
    MESSAGE = @Value(Comment)

FME custom transformer SHAPE Filename

GeometryFilter_Input (input)
    -> SH [GeometryFilter_Input_1]
SH
    GeometryFilter_Point_1 -> GeometryFilter_Area (output)
    GeometryFilter_Line_1 -> GeometryFilter_Null (output)
    GeometryFilter_Area_1 -> GeometryFilter_Line (output)
    GeometryFilter_Null_1 -> GeometryFilter_Point (output)
GeometryFilter_Point (output)
GeometryFilter_Line (output)
GeometryFilter_Area (output)
GeometryFilter_Null (output)
